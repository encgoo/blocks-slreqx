# LLR

## #1: Sum function (Functional)
The sum function shall sum up two inputs.

## #2: Diff function (Functional)
The Diff function shall return the difference between the _first_ input and the second input.

## #3: Two functions (Functional)
The lib shall contain two functions (Sum and Diff).

## #4: Sum error (Functional)
The Sum function shall generate an error "Invalid input" if any of the input is not a number.

## #5: Diff error (Functional)
The Diff function shall generate an error "Invalid inputs" if any of the input is not a number.

## #6: SumDiff lib (Informational)
SumDiff lib is a matlab package.

## #7: Sum range (Functional)

## #8: Diff range (Functional)

## #9: Performance (Functional)
