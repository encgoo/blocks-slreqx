# HLR

## #1: Summary (Informational)
The libs shall include two functions: Sum and Diff.

## #2: Error handling (Informational)

## #3: Sum (Functional)
The lib shall support summing two numbers

## #4: Diff (Functional)
The lib shall support differentiate two numbers.

## #5: Invalid inputs (Functional)
If the inputs are not number, an error message shall be popped up.
